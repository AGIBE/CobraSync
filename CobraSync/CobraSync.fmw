FME workspace CobraSync.fmw
Title: CobraSync

Parameters:
- MSSQL_DATABASE =
- MSSQL_SERVER =
- MSSQL_USERNAME =
- MSSQL_PASSWORD =
- GDBP_DATABASE =
- GDBP_USERNAME =
- GDBP_PASSWORD =
- MYSQL_DATABASE =
- MYSQL_HOST =
- MYSQL_PORT =
- MYSQL_USERNAME =
- MYSQL_PASSWORD =
- PROXY_URL =
- GUIDCOL_FFS =
- LOGFILE =
- EASYSDI_ACCOUNT = 7
- EASYSDI_TEMP_ID = 1

Readers:
- MSSQL_ADO_1: MSSQL_ADO from $(MSSQL_DATABASE)
- ORACLE_NONSPATIAL_1: ORACLE_NONSPATIAL from $(GDBP_DATABASE)

Writers:
- ORACLE_NONSPATIAL_2: ORACLE_NONSPATIAL to $(GDBP_DATABASE)
- ORACLE_NONSPATIAL_3: ORACLE_NONSPATIAL to $(GDBP_DATABASE)
- ORACLE_NONSPATIAL_4: ORACLE_NONSPATIAL to $(GDBP_DATABASE)
- MYSQL_DB_1: MYSQL_DB to $(MYSQL_DATABASE)
- MYSQL_DB_2: MYSQL_DB to $(MYSQL_DATABASE)
- MYSQL_DB_3: MYSQL_DB to $(MYSQL_DATABASE)
- FFS_1: FFS to $(GUIDCOL_FFS)

Note: Cobra
ADDRESSES (reader MSSQL_ADO_1)
    attributes: ID identity, GUID uniqueidentifier, TURNOVER1 money, TURNOVER2 money, TURNOVER3 money, COMPANY1 nvarchar(255), FIRSTNAME0 nvarchar(255), LASTNAME0 nvarchar(255), STREET0 nvarchar(255), COUNTRY0 nvarchar(255), ZIP0 nvarchar(255), CITY0 nvarchar(255), BANKCODE0 nvarchar(255), BIRTHDAY0 nvarchar(100), COMPANY2 nvarchar(255), COMPANY3 nvarchar(255), COMPANY4 nvarchar(255), CREATEDBY nvarchar(100), CUSTOMERNUMBER0 nvarchar(255), DATECREATE datetime, DATEMODIFIED datetime, DATETIME0 datetime, DEPARTMENT0 nvarchar(255), DIRECTPHONE0 nvarchar(255), DUPIDENT nvarchar(255), EMAIL0 nvarchar(255), EMAIL1 nvarchar(255), FAKTURNR0 nvarchar(100), FAX2 nvarchar(255), GECITY0 nvarchar(255),
      GEZIP0 nvarchar(255), INTERNET0 nvarchar(255), ISMANDANT bit, ISPALM bit, KONTO0 nvarchar(255), MAINID integer, MAINSUBMARK nvarchar(100), MANDANT nvarchar(255), MOBILEPHONE1 nvarchar(100), MOBILEPHONE2 nvarchar(255), MODIFIEDBY nvarchar(100), NEXTPRESENTATION0 datetime, NOTES0 ntext, NUMBER0 float, NUMBER1 float, NUMBER2 float, NUMBER3 float, OWNER nvarchar(100), PHONE0 nvarchar(255), POSITION0 nvarchar(255), POSTBOX0 nvarchar(255), POSTBOX1 nvarchar(100), POSTBOXZIP0 nvarchar(255), PRIVATEFLAG bit, PRIVATEMARK bit, PRIVATEPHONE2 nvarchar(255), SALUTATION0 nvarchar(255), SYMBOL0 nvarchar(255), TEXT0 nvarchar(255), TEXT1 nvarchar(255),
      TEXT10 nvarchar(100), TEXT11 nvarchar(255), TEXT12 nvarchar(100), TEXT13 nvarchar(100), TEXT14 nvarchar(100), TEXT15 nvarchar(100), TEXT16 nvarchar(100), TEXT17 nvarchar(100), TEXT18 nvarchar(100), TEXT19 nvarchar(100), TEXT2 nvarchar(255), TEXT20 nvarchar(100), TEXT21 nvarchar(100), TEXT22 nvarchar(100), TEXT23 nvarchar(100), TEXT24 nvarchar(100), TEXT25 nvarchar(100), TEXT26 nvarchar(100), TEXT27 nvarchar(100), TEXT3 nvarchar(255), TEXT4 nvarchar(255), TEXT5 nvarchar(255), TEXT6 nvarchar(255), TEXT7 nvarchar(255), TEXT8 nvarchar(255), TEXT9 nvarchar(255), TITLE0 nvarchar(255), TOPERSON0 nvarchar(255), USERGROUP nvarchar(100), YESNO1 bit,
      YESNO2 bit, YESNO3 bit, YESNO4 bit, YESNO5 bit, YESNO6 bit, YESNO7 bit, YESNO8 bit, TEXT28 nvarchar(255), TEXT29 nvarchar(255), TEXT30 nvarchar(255), TEXT31 nvarchar(255), TEXT32 nvarchar(255), TEXT33 nvarchar(255), TEXT34 nvarchar(255), TEXT35 nvarchar(100), TEXT36 nvarchar(255), STATE1 nvarchar(255), TEXT37 nvarchar(255), TEXT38 nvarchar(255), TEXT39 nvarchar(255), TEXT40 nvarchar(255), TEXT41 nvarchar(255), TEXT42 nvarchar(255), TEXT43 nvarchar(255), TEXT44 nvarchar(255), TEXT45 nvarchar(255), TEXT46 nvarchar(255), YESNO9 bit, YESNO10 bit, YESNO11 bit,
      TEXT47 nvarchar(50), DATE1 datetime, DATE2 datetime, TEXT48 nvarchar(50), TEXT49 nvarchar(150), TEXT50 nvarchar(150), CITY1 nvarchar(150), ZIP1 nvarchar(10), POSITION1 nvarchar(150), STREET1 nvarchar(80)
    -> AttributeKeeper
AttributeKeeper
    KEEP_ATTRS = FAX2,DEPARTMENT0,FIRSTNAME0,INTERNET0,CITY0,ID,STREET0,COMPANY2,MAINSUBMARK,EMAIL0,LASTNAME0,COUNTRY0,POSTBOX0,COMPANY1,PHONE0,DIRECTPHONE0,ZIP0,MAINID,DATEMODIFIED
    -> BulkAttributeRenamer
BulkAttributeRenamer
    ATTRCHOICE = All Attributes
    MODE_CHOICE = RENAME
    PATTERN_ACTION_DISP = ADDPREFIX
    REPLACE_STR = cobra_
    -> FeatureMerger [REQUESTOR]
Note: GeoDBprozess
KONTAKTE (reader ORACLE_NONSPATIAL_1)
    attributes: ID_KONTAKT number(38,0), ID_COBRA number(38,0), AMT varchar2(250), ID_AMTTYP number(38,0), DIENSTELLE varchar2(250), VORNAME varchar2(50), NACHNAME varchar2(50), EMAIL_ADRESSE varchar2(50), ID_KONTAKT1 number(38,0), KUERZEL varchar2(4), FIRMA3 varchar2(250), STATUS varchar2(10), DIREKTION varchar2(50), ID_GEODBMETA varchar2(36), UPDATED timestamp, MAINID number(38,0), MAINSUBMARK number(38,0)
    -> BulkAttributeRenamer_2
BulkAttributeRenamer_2
    ATTRCHOICE = All Attributes
    MODE_CHOICE = RENAME
    PATTERN_ACTION_DISP = ADDPREFIX
    REPLACE_STR = gdbp_
    -> FeatureMerger [SUPPLIER]
Note: Abgleich Cobra und GeoDBprozess. Es sind drei Ergebnisse möglich: / Merged: Kontakt ist sowohl in Cobra als auch GeoDBprozess enthalten. Es handelt sich um einen Kontakt der eventuell aktualisiert werden muss. / NotMerged: Kontakt ist nur in Cobra und nicht in GeoDBprozess enthalten. Es handelt sich somit um einen neuen Kontakt. / Unreferenced: Kontakt ist nicht in Cobra aber in GeoDBprozess enthalten. Es handelt sich um einen bereits archivierten oder noch zu archivierenden Kontakt.
FeatureMerger
    ATTR_ACCUM_MODE = Merge Supplier
    ATTR_CONFLICT_RES = Use Requestor
    IGNORE_NULLS = No
    JOIN_KEYS = @Value(cobra_ID) @Value(gdbp_ID_COBRA) AUTO
    MERGE_TYPE = Attributes Only
    PROCESS_DUPS = No
    REJECT_NULL_MISSING_KEYS = No
    SUPPLIERS_FIRST = No
    MERGED -> AttributeFilter
    NOT_MERGED -> BulkAttributeRenamer_5
    UNREFERENCED -> AttributeKeeper_2
Note: UPDATE
Note: Prüfung des Status. Es sind folgende Optionen möglich: / Empty/Missing/Null/Unfiltered: d.h. das Attribut STATUS ist leer. Das sollte es eigentlich nicht geben. Diese Kontakte können nicht verarbeitet werden und werden geloggt. / 1: Status "ok", dieser Kontakt kann aktualisiert werden. / 2: Status "prüfen": dieser Kontakt darf nicht aktualisiert werden. Er muss von der Normierung geprüft werden. Er wird nicht weiterverarbeitet. / 3: Status "geprüft": dieser Kontakt darf wieder aktualisiert werden. Er wurde von der Normierung geprüft. / 4/5: Status 4 oder 5 darf nur im Falle von archivierten Kontakten vorkommen. Wenn sie hier bei den zu aktualisierenden Kontakten vorkommen, werden sie nicht verarbeitet und geloggt.
AttributeFilter
    ATTR_NAME = gdbp_STATUS
    ATTR_VALUES = <EMPTY>,<MISSING>,<NULL>,<UNFILTERED>,1,2,3,4,5
    <EMPTY> -> AttributeKeeper_14
    <MISSING> -> AttributeKeeper_14
    <NULL> -> AttributeKeeper_14
    <UNFILTERED> -> AttributeKeeper_14
    1 -> Tester_2
    2 -> AttributeKeeper_5
    3 -> AttributeKeeper_7
    4 -> AttributeKeeper_14
    5 -> AttributeKeeper_14
Note: INSERT
Note: ARCHIVE
Note: Test auf substanzielle Änderung / Passed: keine substanzielle Änderung / Failed: substanzielle Änderung
Tester_2
    BOOL_OP = OR
    TEST_CLAUSE:
      TEST @Value(gdbp_AMT) = @Value(cobra_COMPANY1)
      TEST @Value(gdbp_DIENSTELLE) = @Value(cobra_DEPARTMENT0)
      TEST @Value(gdbp_EMAIL_ADRESSE) = @Value(cobra_EMAIL0)
    PASSED -> AttributeKeeper_7
    FAILED -> AttributeKeeper_6

Bookmark: UNGÜLTIGER STATUS
  Diese Features haben einen ungültigen Status. D.h. entweder ist ihr STATUS-Feld leer oder hat die Werte 4 oder 5, die an dieser Stelle nicht gültig sind.
AttributeKeeper_14
    KEEP_ATTRS = gdbp_STATUS,cobra_ID,gdbp_ID_KONTAKT,gdbp_ID_GEODBMETA
    -> Folgende_Features_haben_einen_ungültigen_Status:
Folgende_Features_haben_einen_ungültigen_Status:: Logger
    MAXCOORDS = 20
    MAXFEATS = 500
    MESSAGE = Feature is:

Bookmark: KEIN UPDATE
  Diese Features werden nicht updated, da sie den STATUS=2 haben. D.h. sie müssen zuerst von der Normierung geprüft werden. Dann werden sie von der Normierung den STATUS=3 erhalten, worauf sie dann wieder synchronisiert werden.
AttributeKeeper_5
    KEEP_ATTRS = gdbp_ID_GEODBMETA,gdbp_ID_COBRA,gdbp_ID_KONTAKT
    -> AttributeRenamer_2
AttributeRenamer_2
    ATTR_TABLE:
      RENAME_SET_DEFAULT gdbp_ID_COBRA > ID_COBRA
      RENAME_SET_DEFAULT gdbp_ID_GEODBMETA > ID_GEODBMETA
      RENAME_SET_DEFAULT gdbp_ID_KONTAKT > ID_KONTAKT
    -> Logger
Logger
    MAXCOORDS = 20
    MAXFEATS = 500
    MESSAGE = Folgende Feature haben STATUS=2 und werden daher nicht synchronisiert:

Bookmark: UPDATE normal
  Diese Features werden in GeoDBprozess und GeoDBmeta updated. Egal ob sie geändert haben oder nicht. In GeoDBprozess wird zusätzlich der STATUS fix auf 1 gesetzt.
Note: Nur Cobra-Attribute behalten
AttributeKeeper_7
    KEEP_ATTRS = cobra_FIRSTNAME0,cobra_PHONE0,cobra_LASTNAME0,cobra_STREET0,cobra_EMAIL0,cobra_POSTBOX0,cobra_INTERNET0,gdbp_ID_GEODBMETA,cobra_MAINSUBMARK,cobra_COMPANY1,cobra_ID,cobra_COMPANY2,gdbp_STATUS,cobra_DIRECTPHONE0,gdbp_ID_KONTAKT,gdbp_UPDATED,cobra_CITY0,cobra_COUNTRY0,cobra_DATEMODIFIED,cobra_FAX2,cobra_ZIP0,cobra_MAINID,cobra_DEPARTMENT0
    -> BulkAttributeRenamer_3
BulkAttributeRenamer_3
    ATTRCHOICE = All Attributes
    CASE_DISP = YES
    MODE_CHOICE = RENAME
    PATTERN_ACTION_DISP = REMOVEPREFIX
    REPLACE_STR = cobra_
    -> BulkAttributeRenamer_4
BulkAttributeRenamer_4
    ATTRCHOICE = All Attributes
    CASE_DISP = YES
    MODE_CHOICE = RENAME
    PATTERN_ACTION_DISP = REMOVEPREFIX
    REPLACE_STR = gdbp_
    -> TimeStamper
TimeStamper
    FMT = ISO DateTime (^Y-^m-^dT^H:^M:^S)
    TIME_ATTR = _timestamp
    -> TimeStamper_2
TimeStamper_2
    FMT = FME Date/Time (^Y^m^d^H^M^S)
    TIME_ATTR = modified
    -> TestFilter
Note: Nur Kontakte, die in Cobra seit dem letzten / Update überhaupt aktualisiert wurden, müssen / auch tatsächlich updated werden. Die anderen / können ignoriert werden. / Kontakte mit STATUS=3 müssen aber in jedem / Fall aktualisiert werden, damit sie STATUS=1 / erhalten.
TestFilter
    DEFAULT_VALUE = <UNFILTERED>
    TEST_LIST = BOOL_OP,OR,COMPOSITE_TEST,<Unused>,TEST_CLAUSE,"TEST @Value(STATUS) = 3",ALWAYS_UPDATE,BOOL_OP,OR,COMPOSITE_TEST,<Unused>,TEST_CLAUSE,"TEST @Value(DATEMODIFIED) > @Value(UPDATED)",UPDATE
    ALWAYS_UPDATE -> Tester_3
    ALWAYS_UPDATE -> AttributeRenamer_4
    UPDATE -> Tester_3
    UPDATE -> AttributeRenamer_4
Note: Nur Records mit einer / GeoDBmeta-UUID sollen / dort updated werden.
Tester_3
    BOOL_OP = OR
    TEST_CLAUSE = TEST @Value(ID_GEODBMETA) ATTRIBUTE_HAS_VALUE ""
    PASSED -> AttributeCreator_3
    PASSED -> AttributeManager_2
AttributeCreator_3
    ATTR_TABLE:
      SET_TO metadatastate_id = 3
      SET_TO fme_where = guid='@Value(ID_GEODBMETA)'
    -> XMLTemplater [ROOT]
XMLTemplater
    OUTPUT_XML_HEADER = No
    RESULT_ATTRIBUTE = XML
    ROOT_QUERY_EXPR:
      <gmd:MD_Metadata xmlns:gmd="http://www.isotc211.org/2005/gmd" xmlns:xlink="http://www.w3.org/1999/xlink" xmlns:gts="http://www.isotc211.org/2005/gts" xmlns:srv="http://www.isotc211.org/2005/srv" xmlns:bee="http://www.be.ch/bve/agi/2010/bee" xmlns:che="http://www.geocat.ch/2008/che" xmlns:gco="http://www.isotc211.org/2005/gco" xmlns:gml="http://www.opengis.net/gml" xmlns:geonet="http://www.fao.org/geonetwork">
          <gmd:language>
            <gco:CharacterString>deu</gco:CharacterString>
          </gmd:language>
          <gmd:characterSet>
            <gmd:MD_CharacterSetCode codeListValue="utf8" codeList="http://www.isotc211.org/2005/resources/codeList.xml#MD_CharacterSetCode" />
          </gmd:characterSet>
          <gmd:locale>
            <gmd:PT_Locale id="FR">
              <gmd:languageCode>
                <gmd:LanguageCode codeListValue="fra" codeList="#LanguageCode">Français</gmd:LanguageCode>
              </gmd:languageCode>
              <gmd:characterEncoding>
                <gmd:MD_CharacterSetCode codeListValue="utf8" codeList="#MD_CharacterSetCode">UTF8</gmd:MD_CharacterSetCode>
              </gmd:characterEncoding>
            </gmd:PT_Locale>
          </gmd:locale>
          <gmd:fileIdentifier>
            <gco:CharacterString>{fme:get-attribute("ID_GEODBMETA")}</gco:CharacterString>
          </gmd:fileIdentifier>
          <gmd:datestamp>
            <gco:DateTime>{fme:get-attribute("_timestamp")}</gco:DateTime>
          </gmd:datestamp>
          <gmd:metadataStandardName>
            <gco:CharacterString>ISO 19115:2003/19139 (Profil BE)</gco:CharacterString>
          </gmd:metadataStandardName>
          <gmd:metadataStandardversion>
            <gco:CharacterString>1.0</gco:CharacterString>
          </gmd:metadataStandardversion>
          <bee:cobraIdentifier>
            <gco:Decimal>{fme:get-attribute("ID")}</gco:Decimal>
          </bee:cobraIdentifier>
          <bee:contact>
            <gmd:CI_ResponsibleParty>
              <gmd:individualFirstName>
                <gco:CharacterString>{fme:get-attribute("FIRSTNAME0")}</gco:CharacterString>
              </gmd:individualFirstName>
              <gmd:individualLastName>
                <gco:CharacterString>{fme:get-attribute("LASTNAME0")}</gco:CharacterString>
              </gmd:individualLastName>
              <gmd:organisationName>
                <gco:CharacterString>{fme:get-attribute("COMPANY1")} {fme:get-attribute("COMPANY2")}</gco:CharacterString>
              </gmd:organisationName>
              <gmd:address>
                <gmd:CI_Address>
                  <gmd:streetName>
                    <gco:CharacterString>{fme:get-attribute("STREET0")}</gco:CharacterString>
                  </gmd:streetName>
                  <gmd:addressLine>
                    <gco:CharacterString>{fme:get-attribute("DEPARTMENT0")}</gco:CharacterString>
                  </gmd:addressLine>
                  <gmd:postBox>
                    <gco:Decimal>{fme:get-attribute("POSTBOX0")}</gco:Decimal>
                  </gmd:postBox>
                  <gmd:postalCode>
                    <gco:CharacterString>{fme:get-attribute("ZIP0")}</gco:CharacterString>
                  </gmd:postalCode>
                  <gmd:city>
                    <gco:CharacterString>{fme:get-attribute("CITY0")}</gco:CharacterString>
                  </gmd:city>
                  <gmd:country>
                    <gmd:CountryCodeISO>{fme:get-attribute("COUNTRY0")}</gmd:CountryCodeISO>
                  </gmd:country>
                </gmd:CI_Address>
              </gmd:address>
              <gmd:phone>
                <gmd:CI_Telephone>
                  <gmd:number>
                    <gco:CharacterString>{fme:get-attribute("PHONE0")}</gco:CharacterString>
                  </gmd:number>
                  <gmd:numberType>
                    <gmd:CI_NumberTypeCode codeListValue="mainNumber" codeList="http://www.isotc211.org/2005/resources/codeList.xml#CI_NumberTypeCode" />
                  </gmd:numberType>
                </gmd:CI_Telephone>
              </gmd:phone>
              <gmd:phone>
                <gmd:CI_Telephone>
                  <gmd:number>
                    <gco:CharacterString>{fme:get-attribute("DIRECTPHONE0")}</gco:CharacterString>
                  </gmd:number>
                  <gmd:numberType>
                    <gmd:CI_NumberTypeCode codeListValue="directNumber" codeList="http://www.isotc211.org/2005/resources/codeList.xml#CI_NumberTypeCode" />
                  </gmd:numberType>
                </gmd:CI_Telephone>
              </gmd:phone>
              <gmd:phone>
                <gmd:CI_Telephone>
                  <gmd:number>
                    <gco:CharacterString>{fme:get-attribute("FAX2")}</gco:CharacterString>
                  </gmd:number>
                  <gmd:numberType>
                    <gmd:CI_NumberTypeCode codeListValue="facsimile" codeList="http://www.isotc211.org/2005/resources/codeList.xml#CI_NumberTypeCode" />
                  </gmd:numberType>
                </gmd:CI_Telephone>
              </gmd:phone>
              <gmd:electronicalMailAddress>
                <gco:CharacterString>{fme:get-attribute("EMAIL0")}</gco:CharacterString>
              </gmd:electronicalMailAddress>
              <gmd:linkage>
                <gco:CharacterString>{fme:get-attribute("INTERNET0")}</gco:CharacterString>
                <gmd:PT_FreeText>
                  <gmd:textGroup>
                    <gmd:LocalisedCharacterString locale="#FR">{fme:get-attribute("INTERNET0")}</gmd:LocalisedCharacterString>
                  </gmd:textGroup>
                </gmd:PT_FreeText>
              </gmd:linkage>
            </gmd:CI_ResponsibleParty>
          </bee:contact>
        </gmd:MD_Metadata>
    VISIBLE_QUERY_VALIDATE = Yes
    -> AttributeKeeper_8
AttributeKeeper_8
    KEEP_ATTRS = XML,metadatastate_id,modified,fme_where,ID_GEODBMETA
    -> SQLExecutor [INITIATOR]
SQLExecutor
    COMBINE_ATTRS = Keep Initiator Attributes if Conflict
    COMBINE_GEOM = Initiator Geometry Only
    DATASET = $(MYSQL_DATABASE)
    EXPOSED_ATTRIBUTE_LIST = version_id
    FORMAT = MYSQL
    MYSQL_HOST = $(MYSQL_HOST)
    MYSQL_PASSWORD = $(MYSQL_PASSWORD)
    MYSQL_PORT = $(MYSQL_PORT)
    MYSQL_QUERY_FEATURE_TYPES_FOR_MERGE_FILTERS = Yes
    MYSQL_USER_NAME = $(MYSQL_USERNAME)
    SQL_STATEMENT = select version_id from jos_sdi_metadata where guid='@Value(ID_GEODBMETA)'
    RESULT -> StringConcatenator
    RESULT -> jos_sdi_metadata (writer MYSQL_DB_2)
Note: jos_sdi_metadata
jos_sdi_metadata (writer MYSQL_DB_2)
    attributes: modified datetime, metadatastate_id int
StringConcatenator
    ACTION = Create New Attribute
    PARM_LINE = id=@Value(version_id)
    VAL_ATTR = fme_where
    -> SQLExecutor_2 [INITIATOR]
SQLExecutor_2
    COMBINE_ATTRS = Keep Initiator Attributes if Conflict
    COMBINE_GEOM = Initiator Geometry Only
    DATASET = $(MYSQL_DATABASE)
    EXPOSED_ATTRIBUTE_LIST = resource_id
    FORMAT = MYSQL
    MYSQL_HOST = $(MYSQL_HOST)
    MYSQL_PASSWORD = $(MYSQL_PASSWORD)
    MYSQL_PORT = $(MYSQL_PORT)
    MYSQL_QUERY_FEATURE_TYPES_FOR_MERGE_FILTERS = Yes
    MYSQL_USER_NAME = $(MYSQL_USERNAME)
    SQL_STATEMENT = select resource_id from jos_sdi_version where id='@Value(version_id)'
    RESULT -> StringConcatenator_2
    RESULT -> jos_sdi_version (writer MYSQL_DB_2)
Note: jos_sdi_version
jos_sdi_version (writer MYSQL_DB_2)
    attributes: modified datetime
StringConcatenator_2
    ACTION = Create New Attribute
    PARM_LINE = id=@Value(resource_id)
    VAL_ATTR = fme_where
    -> jos_sdi_resource (writer MYSQL_DB_2)
    -> AttributeKeeper_9
Note: jos_sdi_resource
jos_sdi_resource (writer MYSQL_DB_2)
    attributes: modified datetime
AttributeKeeper_9
    KEEP_ATTRS = XML,ID_GEODBMETA
    -> PythonCaller
Note: Update Request aufbauen
PythonCaller
    NEW_ATTRIBUTES = _request
    PYTHONSOURCE:
      import fme
      import fmeobjects

      def processFeature(feature):
          logger = fmeobjects.FMELogFile()
          guid = feature.getAttribute('ID_GEODBMETA')
          metadata = feature.getAttribute('XML')

          if guid is None:
              logger.logMessageString("CSWInsertRequestor: guid Required", fmeobjects.FME_ERROR)
              return

          request = u"""
              <csw:Transaction service="CSW" version="2.0.2" xmlns:csw="http://www.opengis.net/cat/csw/2.0.2" xmlns:ogc="http://www.opengis.net/ogc">
      	<csw:Update>
              %s
          <csw:Constraint version="1.1.0">
            <ogc:Filter>
              <ogc:PropertyIsEqualTo>
                <ogc:PropertyName>fileId</ogc:PropertyName>
                <ogc:Literal>%s</ogc:Literal>
              </ogc:PropertyIsEqualTo>
            </ogc:Filter>
          </csw:Constraint>
      	</csw:Update>
              </csw:Transaction>
              """ % (metadata,guid)

          feature.setAttribute("_request", request)
    PYTHONSYMBOL = processFeature
    -> HTTPCaller
AttributeManager_2
    ATTR_TABLE:
      RENAME_SET_VALUE ID > COBRA_ID
      RENAME_SET_VALUE FIRSTNAME0 > FIRSTNAME
      RENAME_SET_VALUE LASTNAME0 > LASTNAME
      RENAME_SET_VALUE STREET0 > STREETNAME
      RENAME_SET_VALUE COUNTRY0 > COUNTRY
      RENAME_SET_VALUE ZIP0 > POSTALCODE
      RENAME_SET_VALUE CITY0 > CITY
      REMOVE DATEMODIFIED
      RENAME_SET_VALUE DEPARTMENT0 > ADDRESSLINE
      RENAME_SET_VALUE DIRECTPHONE0 > PHONEDIRECT
      RENAME_SET_VALUE EMAIL0 > EMAIL
      RENAME_SET_VALUE FAX2 > FAX
      RENAME_SET_VALUE INTERNET0 > INTERNET
      REMOVE MAINID
      REMOVE MAINSUBMARK
      RENAME_SET_VALUE PHONE0 > PHONEMAIN
      RENAME_SET_VALUE POSTBOX0 > POSTBOX
      REMOVE _timestamp
      RENAME_SET_VALUE ID_GEODBMETA > CONTACT_UUID
    -> StringConcatenator_4
StringConcatenator_4
    ACTION = Create New Attribute
    PARM_LINE = @Value(COMPANY1) @Value(COMPANY2)
    VAL_ATTR = ORGANISATION
    -> AttributeCreator_11
AttributeCreator_11
    ATTR_TABLE = SET_TO fme_db_operation = UPDATE
    -> META_CONTACT_DETAILS (writer ORACLE_NONSPATIAL_3)
Note: Infotabellen updaten
META_CONTACT_DETAILS (writer ORACLE_NONSPATIAL_3)
    attributes: CONTACT_UUID nvarchar(255), COBRA_ID nvarchar(255), FIRSTNAME nvarchar(255), LASTNAME nvarchar(255), ORGANISATION nvarchar(255), STREETNAME nvarchar(255), ADDRESSLINE nvarchar(255), POSTBOX nvarchar(255), POSTALCODE nvarchar(255), CITY nvarchar(255), COUNTRY nvarchar(255), PHONEMAIN nvarchar(255), PHONEDIRECT nvarchar(255), FAX nvarchar(255), EMAIL nvarchar(255), INTERNET nvarchar(255)
AttributeRenamer_4
    ATTR_TABLE:
      RENAME_SET_DEFAULT ID > ID_COBRA
      RENAME_SET_DEFAULT COMPANY1 > AMT
      RENAME_SET_DEFAULT DEPARTMENT0 > DIENSTELLE
      RENAME_SET_DEFAULT FIRSTNAME0 > VORNAME
      RENAME_SET_DEFAULT LASTNAME0 > NACHNAME
      RENAME_SET_DEFAULT EMAIL0 > EMAIL_ADRESSE
      RENAME_SET_DEFAULT COMPANY2 > FIRMA3
    -> AttributeKeeper_10
AttributeKeeper_10
    KEEP_ATTRS = MAINID,FIRMA3,EMAIL_ADRESSE,VORNAME,DIENSTELLE,ID_KONTAKT,NACHNAME,ID_GEODBMETA,MAINSUBMARK,ID_COBRA,AMT
    -> AttributeCreator_4
AttributeCreator_4
    ATTR_TABLE:
      SET_TO STATUS = 1
      SET_TO fme_db_operation = UPDATE
    -> TimeStamper_3
TimeStamper_3
    FMT = FME Date/Time (^Y^m^d^H^M^S)
    TIME_ATTR = UPDATED
    -> KONTAKTE (writer ORACLE_NONSPATIAL_3)
Note: GDBP.KONTAKTE
KONTAKTE (writer ORACLE_NONSPATIAL_3)
    attributes: ID_KONTAKT number(38,0), ID_COBRA number(38,0), AMT varchar2(250), DIENSTELLE varchar2(250), VORNAME varchar2(50), NACHNAME varchar2(50), EMAIL_ADRESSE varchar2(50), FIRMA3 varchar2(250), STATUS varchar2(10), ID_GEODBMETA varchar2(36), UPDATED timestamp, MAINID number(38,0), MAINSUBMARK varchar2(4)

Bookmark: UPDATE GDBP.KONTAKTE.STATUS=2
  Diese Features weisen eine substanzielle Änderung auf (evtl. infolge einer Pensionierung oder eines Austritts). Sie dürfen nicht mehr synchronisiert werden. Stattdessen erhalten sie neu den STATUS=2. Sie werden nun von der Normierung geprüft.
AttributeKeeper_6
    KEEP_ATTRS = gdbp_ID_KONTAKT
    -> AttributeCreator_2
AttributeCreator_2
    ATTR_TABLE:
      SET_TO fme_db_operation = UPDATE
      SET_TO STATUS = 2
    -> AttributeRenamer_3
AttributeRenamer_3
    ATTR_TABLE = RENAME_SET_DEFAULT gdbp_ID_KONTAKT > ID_KONTAKT
    -> KONTAKTE (writer ORACLE_NONSPATIAL_2)

Bookmark: NEUER KONTAKT: INSERT
  Diese Kontakte werden in GeoDBprozess und GeoDBmeta neu angelegt. Es wird nicht geprüft, ob diese Kontakte in GeoDBprozess oder GeoDBmeta bereits existieren. Es wird immer ein neuer Kontakt angelegt!
BulkAttributeRenamer_5
    ATTRCHOICE = All Attributes
    CASE_DISP = YES
    MODE_CHOICE = RENAME
    PATTERN_ACTION_DISP = REMOVEPREFIX
    REPLACE_STR = cobra_
    -> UUIDGenerator
UUIDGenerator
    UUID_ATTR = metadata_guid
    -> UUIDGenerator_2
UUIDGenerator_2
    UUID_ATTR = version_guid
    -> UUIDGenerator_3
UUIDGenerator_3
    UUID_ATTR = resource_guid
    -> TimeStamper_4
TimeStamper_4
    FMT = ISO DateTime (^Y-^m-^dT^H:^M:^S)
    TIME_ATTR = _timestamp
    -> TimeStamper_5
    -> XMLTemplater_2 [ROOT]
    -> AttributeManager
XMLTemplater_2
    OUTPUT_XML_HEADER = No
    RESULT_ATTRIBUTE = XML
    ROOT_QUERY_EXPR:
      <gmd:MD_Metadata xmlns:gmd="http://www.isotc211.org/2005/gmd" xmlns:xlink="http://www.w3.org/1999/xlink" xmlns:gts="http://www.isotc211.org/2005/gts" xmlns:srv="http://www.isotc211.org/2005/srv" xmlns:bee="http://www.be.ch/bve/agi/2010/bee" xmlns:che="http://www.geocat.ch/2008/che" xmlns:gco="http://www.isotc211.org/2005/gco" xmlns:gml="http://www.opengis.net/gml" xmlns:geonet="http://www.fao.org/geonetwork">
          <gmd:language>
            <gco:CharacterString>deu</gco:CharacterString>
          </gmd:language>
          <gmd:characterSet>
            <gmd:MD_CharacterSetCode codeListValue="utf8" codeList="http://www.isotc211.org/2005/resources/codeList.xml#MD_CharacterSetCode" />
          </gmd:characterSet>
          <gmd:locale>
            <gmd:PT_Locale id="FR">
              <gmd:languageCode>
                <gmd:LanguageCode codeListValue="fra" codeList="#LanguageCode">Français</gmd:LanguageCode>
              </gmd:languageCode>
              <gmd:characterEncoding>
                <gmd:MD_CharacterSetCode codeListValue="utf8" codeList="#MD_CharacterSetCode">UTF8</gmd:MD_CharacterSetCode>
              </gmd:characterEncoding>
            </gmd:PT_Locale>
          </gmd:locale>
          <gmd:fileIdentifier>
            <gco:CharacterString>{fme:get-attribute("metadata_guid")}</gco:CharacterString>
          </gmd:fileIdentifier>
          <gmd:datestamp>
            <gco:DateTime>{fme:get-attribute("_timestamp")}</gco:DateTime>
          </gmd:datestamp>
          <gmd:metadataStandardName>
            <gco:CharacterString>ISO 19115:2003/19139 (Profil BE)</gco:CharacterString>
          </gmd:metadataStandardName>
          <gmd:metadataStandardversion>
            <gco:CharacterString>1.0</gco:CharacterString>
          </gmd:metadataStandardversion>
          <bee:cobraIdentifier>
            <gco:Decimal>{fme:get-attribute("ID")}</gco:Decimal>
          </bee:cobraIdentifier>
          <bee:contact>
            <gmd:CI_ResponsibleParty>
              <gmd:individualFirstName>
                <gco:CharacterString>{fme:get-attribute("FIRSTNAME0")}</gco:CharacterString>
              </gmd:individualFirstName>
              <gmd:individualLastName>
                <gco:CharacterString>{fme:get-attribute("LASTNAME0")}</gco:CharacterString>
              </gmd:individualLastName>
              <gmd:organisationName>
                <gco:CharacterString>{fme:get-attribute("COMPANY1")} {fme:get-attribute("COMPANY2")}</gco:CharacterString>
              </gmd:organisationName>
              <gmd:address>
                <gmd:CI_Address>
                  <gmd:streetName>
                    <gco:CharacterString>{fme:get-attribute("STREET0")}</gco:CharacterString>
                  </gmd:streetName>
                  <gmd:addressLine>
                    <gco:CharacterString>{fme:get-attribute("DEPARTMENT0")}</gco:CharacterString>
                  </gmd:addressLine>
                  <gmd:postBox>
                    <gco:Decimal>{fme:get-attribute("POSTBOX0")}</gco:Decimal>
                  </gmd:postBox>
                  <gmd:postalCode>
                    <gco:CharacterString>{fme:get-attribute("ZIP0")}</gco:CharacterString>
                  </gmd:postalCode>
                  <gmd:city>
                    <gco:CharacterString>{fme:get-attribute("CITY0")}</gco:CharacterString>
                  </gmd:city>
                  <gmd:country>
                    <gmd:CountryCodeISO>{fme:get-attribute("COUNTRY0")}</gmd:CountryCodeISO>
                  </gmd:country>
                </gmd:CI_Address>
              </gmd:address>
              <gmd:phone>
                <gmd:CI_Telephone>
                  <gmd:number>
                    <gco:CharacterString>{fme:get-attribute("PHONE0")}</gco:CharacterString>
                  </gmd:number>
                  <gmd:numberType>
                    <gmd:CI_NumberTypeCode codeListValue="mainNumber" codeList="http://www.isotc211.org/2005/resources/codeList.xml#CI_NumberTypeCode" />
                  </gmd:numberType>
                </gmd:CI_Telephone>
              </gmd:phone>
              <gmd:phone>
                <gmd:CI_Telephone>
                  <gmd:number>
                    <gco:CharacterString>{fme:get-attribute("DIRECTPHONE0")}</gco:CharacterString>
                  </gmd:number>
                  <gmd:numberType>
                    <gmd:CI_NumberTypeCode codeListValue="directNumber" codeList="http://www.isotc211.org/2005/resources/codeList.xml#CI_NumberTypeCode" />
                  </gmd:numberType>
                </gmd:CI_Telephone>
              </gmd:phone>
              <gmd:phone>
                <gmd:CI_Telephone>
                  <gmd:number>
                    <gco:CharacterString>{fme:get-attribute("FAX2")}</gco:CharacterString>
                  </gmd:number>
                  <gmd:numberType>
                    <gmd:CI_NumberTypeCode codeListValue="facsimile" codeList="http://www.isotc211.org/2005/resources/codeList.xml#CI_NumberTypeCode" />
                  </gmd:numberType>
                </gmd:CI_Telephone>
              </gmd:phone>
              <gmd:electronicalMailAddress>
                <gco:CharacterString>{fme:get-attribute("EMAIL0")}</gco:CharacterString>
              </gmd:electronicalMailAddress>
              <gmd:linkage>
                <gco:CharacterString>{fme:get-attribute("INTERNET0")}</gco:CharacterString>
                <gmd:PT_FreeText>
                  <gmd:textGroup>
                    <gmd:LocalisedCharacterString locale="#FR">{fme:get-attribute("INTERNET0")}</gmd:LocalisedCharacterString>
                  </gmd:textGroup>
                </gmd:PT_FreeText>
              </gmd:linkage>
            </gmd:CI_ResponsibleParty>
          </bee:contact>
        </gmd:MD_Metadata>
    VISIBLE_QUERY_VALIDATE = Yes
    -> AttributeKeeper_11
AttributeKeeper_11
    KEEP_ATTRS = metadata_guid,XML
    -> PythonCaller_2
Note: Insert Request aufbauen
PythonCaller_2
    NEW_ATTRIBUTES = _request
    PYTHONSOURCE:
      import fme
      import fmeobjects

      def processFeature(feature):
          logger = fmeobjects.FMELogFile()
          metadata = feature.getAttribute('XML')

          request = u"""
              <csw:Transaction service="CSW" version="2.0.2" xmlns:csw="http://www.opengis.net/cat/csw/2.0.2">
      	<csw:Insert>
              %s
      	</csw:Insert>
              </csw:Transaction>
              """ % (metadata)

          feature.setAttribute("_request", request)
    PYTHONSYMBOL = processFeature
    -> HTTPCaller
AttributeManager
    ATTR_TABLE:
      RENAME_SET_VALUE ID > COBRA_ID
      RENAME_SET_VALUE FIRSTNAME0 > FIRSTNAME
      RENAME_SET_VALUE LASTNAME0 > LASTNAME
      RENAME_SET_VALUE STREET0 > STREETNAME
      RENAME_SET_VALUE COUNTRY0 > COUNTRY
      RENAME_SET_VALUE ZIP0 > POSTALCODE
      RENAME_SET_VALUE CITY0 > CITY
      REMOVE DATEMODIFIED
      RENAME_SET_VALUE DEPARTMENT0 > ADDRESSLINE
      RENAME_SET_VALUE DIRECTPHONE0 > PHONEDIRECT
      RENAME_SET_VALUE EMAIL0 > EMAIL
      RENAME_SET_VALUE FAX2 > FAX
      RENAME_SET_VALUE INTERNET0 > INTERNET
      REMOVE MAINID
      REMOVE MAINSUBMARK
      RENAME_SET_VALUE PHONE0 > PHONEMAIN
      RENAME_SET_VALUE POSTBOX0 > POSTBOX
      RENAME_SET_VALUE metadata_guid > CONTACT_UUID
      REMOVE version_guid
      REMOVE resource_guid
      REMOVE _timestamp
    -> StringConcatenator_3
StringConcatenator_3
    ACTION = Create New Attribute
    PARM_LINE = @Value(COMPANY1) @Value(COMPANY2)
    VAL_ATTR = ORGANISATION
    -> META_CONTACT_DETAILS (writer ORACLE_NONSPATIAL_4)
Note: Infotabellen abfüllen
META_CONTACT_DETAILS (writer ORACLE_NONSPATIAL_4)
    attributes: CONTACT_UUID nvarchar(255), COBRA_ID nvarchar(255), FIRSTNAME nvarchar(255), LASTNAME nvarchar(255), ORGANISATION nvarchar(255), STREETNAME nvarchar(255), ADDRESSLINE nvarchar(255), POSTBOX nvarchar(255), POSTALCODE nvarchar(255), CITY nvarchar(255), COUNTRY nvarchar(255), PHONEMAIN nvarchar(255), PHONEDIRECT nvarchar(255), FAX nvarchar(255), EMAIL nvarchar(255), INTERNET nvarchar(255)
TimeStamper_5
    FMT = FME Date/Time (^Y^m^d^H^M^S)
    TIME_ATTR = created
    -> AttributeCreator_5
    -> AttributeRenamer_6
Note: Alle möglichen EasySDI-Werte setzen. / Die meisten wurden aus dem Vorgänger- / Script übernommen. Die Bedeutung der / meisten Werte ist nicht bekannt. Mit den / gewählten Werten scheint EasySDI gut / zu funktionieren.
AttributeCreator_5
    ATTR_TABLE:
      SET_TO state = 1
      SET_TO access = 1
      SET_TO asset_id = 0
      SET_TO created_by = $(EASYSDI_ACCOUNT)
      SET_TO modified_by = $(EASYSDI_ACCOUNT)
      SET_TO modified = @Value(created)
      SET_TO ordering = 0
      SET_TO checked_out = 0
      SET_TO accessscope_id = 1
      SET_TO published = @Value(created)
      SET_TO organism_id = 4
      SET_TO resourcetype_id = 9
      SET_TO metadatastate_id = 3
      SET_TO checked_out_time = 00000000000000
      SET_TO name = FME_CONDITIONAL:DEFAULT_VALUE'@Value(DEPARTMENT0) @Value(COMPANY2) @Value(COMPANY1)'BOOL_OP;OR;COMPOSITE_TEST;<Unused>;TEST @Value(FIRSTNAME0) ATTRIBUTE_HAS_VALUE _FME_BLANK_STRING_;TEST @Value(LASTNAME0) ATTRIBUTE_HAS_VALUE _FME_BLANK_STRING_'@Value(LASTNAME0) @Value(FIRSTNAME0)'FME_NUM_CONDITIONS2___
      SET_TO resource_id = $(EASYSDI_TEMP_ID)
      SET_TO version_id = $(EASYSDI_TEMP_ID)
      SET_TO notification = 0
      SET_TO endpublished = 00000000000000
      SET_TO archived = 00000000000000
    -> AttributeTrimmer
AttributeTrimmer
    SRC_ATTRS = name
    TRIM_CHARS = " "
    TRIM_TO_NONE = Yes
    TRIM_TYPE = Both
    -> AttributeCreator_6
AttributeCreator_6
    ATTR_TABLE:
      SET_TO alias = @Value(name)
      SET_TO description = @Value(name)
      SET_TO guid = @Value(resource_guid)
    -> AttributeKeeper_12
    -> jos_sdi_resource (writer MYSQL_DB_3)
    -> AttributeCreator_7
    -> AttributeCreator_9
Note: jos_sdi_resource
jos_sdi_resource (writer MYSQL_DB_3)
    attributes: guid varchar(36), alias varchar(50), created_by int, created datetime, modified datetime, ordering int, state tinyint, checked_out int, checked_out_time datetime, name varchar(255), description varchar(500), organism_id int, resourcetype_id int, accessscope_id int, access int, asset_id int
AttributeCreator_7
    ATTR_TABLE:
      SET_TO name = @Value(created)
      SET_TO alias = @Value(created)
      SET_TO guid = @Value(version_guid)
    -> jos_sdi_version (writer MYSQL_DB_3)
Note: jos_sdi_version
jos_sdi_version (writer MYSQL_DB_3)
    attributes: guid varchar(36), alias varchar(50), created_by int, created datetime, modified_by int, modified datetime, ordering int, state tinyint, checked_out int, checked_out_time datetime, name varchar(255), resource_id int, access int, asset_id int
AttributeCreator_9
    ATTR_TABLE = SET_TO guid = @Value(metadata_guid)
    -> jos_sdi_metadata (writer MYSQL_DB_3)
Note: jos_sdi_metadata
jos_sdi_metadata (writer MYSQL_DB_3)
    attributes: guid varchar(36), created_by int, created datetime, modified_by int, modified datetime, ordering int, metadatastate_id int, checked_out int, checked_out_time datetime, accessscope_id int, published datetime, endpublished datetime, archived datetime, notification tinyint, version_id int, access int, asset_id int
AttributeKeeper_12
    KEEP_ATTRS = resource_guid,metadata_guid,version_guid
    -> AttributeRenamer_5
AttributeRenamer_5
    ATTR_TABLE:
      RENAME_SET_DEFAULT metadata_guid > guid_meta
      RENAME_SET_DEFAULT resource_guid > guid_obj
      RENAME_SET_DEFAULT version_guid > guid_ver
    -> GUIDCOL (writer FFS_1)
Note: In den Tabellen jos_sdi_metadata (version_id) und jos_sdi_version (resource_id) sind Foreign Keys auf andere Tabellen enthalten. Die korrekten IDs sind aber erst bekannt, wenn die Features in die DB geschrieben wurden. Also nicht zur Laufzeit der Workbench! Deshalb werden temporäre IDs geschrieben sowie alle beteiligten UUIDs in ein temporäres FFS-File geschrieben. Dieses File wird im Anschluss an diese Workbench von einer weiteren Workbench eingelesen und trägt die korrekten IDs in die Tabellen ein.
GUIDCOL (writer FFS_1)
    attributes: guid_meta varchar(200), guid_obj varchar(200), guid_ver varchar(200)
AttributeRenamer_6
    ATTR_TABLE:
      RENAME_SET_DEFAULT ID > ID_COBRA
      RENAME_SET_DEFAULT COMPANY1 > AMT
      RENAME_SET_DEFAULT DEPARTMENT0 > DIENSTELLE
      RENAME_SET_DEFAULT FIRSTNAME0 > VORNAME
      RENAME_SET_DEFAULT LASTNAME0 > NACHNAME
      RENAME_SET_DEFAULT EMAIL0 > EMAIL_ADRESSE
      RENAME_SET_DEFAULT COMPANY2 > FIRMA3
      RENAME_SET_DEFAULT metadata_guid > ID_GEODBMETA
      RENAME_SET_DEFAULT created > UPDATED
    -> AttributeKeeper_13
AttributeKeeper_13
    KEEP_ATTRS = MAINID,FIRMA3,EMAIL_ADRESSE,VORNAME,UPDATED,DIENSTELLE,NACHNAME,ID_GEODBMETA,MAINSUBMARK,ID_COBRA,AMT
    -> AttributeCreator_8
AttributeCreator_8
    ATTR_TABLE:
      SET_TO STATUS = 1
      SET_TO AMT_ORI = @Value(AMT)
    -> StringReplacer
Note: Allfällige ' im Feld AMT müssen / escaped werden, damit es bei / den Oracle-Abfragen keine / Fehler gibt.
StringReplacer
    CASE = NO
    FIND_TEXT = '
    NO_MATCH = _FME_NO_OP_
    REGEXP = NO
    REPLACE_TEXT = ''
    SRC_ATTRS = AMT
    -> SQLExecutor_3 [INITIATOR]
Note: ID_AMTTYP abfüllen
SQLExecutor_3
    COMBINE_ATTRS = Keep Initiator Attributes if Conflict
    COMBINE_GEOM = Initiator Geometry Only
    DATASET = $(GDBP_DATABASE)
    EXPOSED_ATTRIBUTE_LIST = ID_AMTTYP
    FORMAT = ORACLE_NONSPATIAL
    ORACLE_NONSPATIAL_PASSWORD = $(GDBP_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(GDBP_USERNAME)
    ORACLE_NONSPATIAL_USE_UNIFIED_DATE_ATTRS = YES
    SQL_STATEMENT = select ID_AMTTYP FROM (select ID_AMTTYP from GDBP.KONTAKTE where AMT='@Value(AMT)' order by ID_AMTTYP asc) where rownum=1
    RESULT -> AttributeRemover
    INITIATOR -> Tester_5
Tester_5
    BOOL_OP = OR
    TEST_CLAUSE = TEST @Value(_matched_records) = 0
    PASSED -> AttributeRemover
AttributeRemover
    REMOVE_ATTRS = _matched_records
    -> SQLExecutor_4 [INITIATOR]
Note: ID_KONTAKT1 abfüllen
SQLExecutor_4
    COMBINE_ATTRS = Keep Initiator Attributes if Conflict
    COMBINE_GEOM = Initiator Geometry Only
    DATASET = $(GDBP_DATABASE)
    EXPOSED_ATTRIBUTE_LIST = ID_KONTAKT1
    FORMAT = ORACLE_NONSPATIAL
    ORACLE_NONSPATIAL_PASSWORD = $(GDBP_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(GDBP_USERNAME)
    ORACLE_NONSPATIAL_USE_UNIFIED_DATE_ATTRS = YES
    SQL_STATEMENT = select ID_KONTAKT1 from kontakte where amt='@Value(AMT)' and id_kontakt1 > 1 and rownum=1
    RESULT -> AttributeRemover_2
    INITIATOR -> Tester_6
Tester_6
    BOOL_OP = OR
    TEST_CLAUSE = TEST @Value(_matched_records) = 0
    PASSED -> AttributeRemover_2
AttributeRemover_2
    REMOVE_ATTRS = _matched_records
    -> SQLExecutor_5 [INITIATOR]
Note: DIREKTION abfüllen
SQLExecutor_5
    COMBINE_ATTRS = Keep Initiator Attributes if Conflict
    COMBINE_GEOM = Initiator Geometry Only
    DATASET = $(GDBP_DATABASE)
    EXPOSED_ATTRIBUTE_LIST = DIREKTION
    FORMAT = ORACLE_NONSPATIAL
    ORACLE_NONSPATIAL_PASSWORD = $(GDBP_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(GDBP_USERNAME)
    ORACLE_NONSPATIAL_USE_UNIFIED_DATE_ATTRS = YES
    SQL_STATEMENT = select DIREKTION FROM (select DIREKTION from KONTAKTE where AMT='@Value(AMT)' order by DIENSTELLE desc) where rownum=1
    RESULT -> AttributeRemover_3
    INITIATOR -> Tester_7
Tester_7
    BOOL_OP = OR
    TEST_CLAUSE = TEST @Value(_matched_records) = 0
    PASSED -> AttributeRemover_3
AttributeRemover_3
    REMOVE_ATTRS = AMT,_matched_records
    -> AttributeRenamer_7
AttributeRenamer_7
    ATTR_TABLE = RENAME_SET_DEFAULT AMT_ORI > AMT
    -> KONTAKTE (writer ORACLE_NONSPATIAL_4)
Note: GDBP.KONTAKTE
Note: GDBP.KONTAKTE
KONTAKTE (writer ORACLE_NONSPATIAL_4)
    attributes: ID_COBRA number(38,0), AMT varchar2(250), ID_AMTTYP number(38,0), DIENSTELLE varchar2(250), VORNAME varchar2(50), NACHNAME varchar2(50), EMAIL_ADRESSE varchar2(50), ID_KONTAKT1 number(38,0), KUERZEL varchar2(4), FIRMA3 varchar2(250), STATUS varchar2(10), DIREKTION varchar2(50), ID_GEODBMETA varchar2(36), UPDATED timestamp, MAINID number(38,0), MAINSUBMARK varchar2(4)

Bookmark: CSW-TRANSACTION (EASYSDI PROXY)
HTTPCaller
    CONNECTION_TIMEOUT_LENGTH = 60
    ERROR_ATTR = _error
    FOLLOW_REDIRECTS = Yes
    HTTP_METHOD = POST
    RESPONSE_HEADER_LIST_ATTR = _headers
    SAVE_FILE = Attribute
    STATUS_CODE_ATTR = _http_status_code
    TARGET_ATTR = _response_body
    TARGET_ATTR_ENCODING = auto-detect
    TARGET_URL = $(PROXY_URL)
    TRANSFER_TIMEOUT_LENGTH = 90
    UPLOAD_BODY = @Value(_request)
    UPLOAD_CONTENT_TYPE = XML (application/xml)
    UPLOAD_TYPE = Specify Upload Body
    USE_COOKIES = No
    VERIFY_SSL_CERTIFICATES = Yes
    -> StringSearcher
    <Rejected> -> Terminator
StringSearcher
    CASE = no
    MATCHED_RESULT_ATTR = _first_match
    REGEXP = "TransactionResponse "
    STRING_TO_SEARCH = @Value(_response_body)
    MATCHED -> Logger_2
    NOT_MATCHED -> Terminator
Logger_2
    MAXCOORDS = 20
    MAXFEATS = 500
    MESSAGE = POST zum Proxy-Server war erfolgreich:
Terminator
    MESSAGE = Fehler beim POST-Request am Proxy:

Bookmark: ARCHIVIEREN
  Alle Kontakte, die hier landen, existieren in GeoDBprozess aber nicht (mehr) in Cobra. D.h. sie müssen in GeoDBprozess und GeoDBmeta archiviert werden.
AttributeKeeper_2
    KEEP_ATTRS = gdbp_ID_GEODBMETA,gdbp_ID_KONTAKT
    -> AttributeRenamer
AttributeRenamer
    ATTR_TABLE = RENAME_SET_DEFAULT gdbp_ID_KONTAKT > ID_KONTAKT
    -> AttributeCreator
AttributeCreator
    ATTR_TABLE:
      SET_TO STATUS = 5
      SET_TO fme_db_operation = UPDATE
    -> AttributeKeeper_3
    -> AttributeCreator_10
AttributeKeeper_3
    KEEP_ATTRS = STATUS,ID_KONTAKT,fme_db_operation
    -> KONTAKTE (writer ORACLE_NONSPATIAL_2)
Note: GeoDBprozess / fme_db_operation muss / vorhanden sein!
KONTAKTE (writer ORACLE_NONSPATIAL_2)
    attributes: ID_KONTAKT number(38,0), STATUS number(10,10)
AttributeCreator_10
    ATTR_TABLE:
      SET_TO metadatastate_id = 4
      SET_TO fme_where = guid='@Value(gdbp_ID_GEODBMETA)'
    -> Tester
Note: Nur Records mit einer / GeoDBmeta-UUID sollen / dort updated werden.
Tester
    BOOL_OP = OR
    TEST_CLAUSE = TEST @Value(gdbp_ID_GEODBMETA) ATTRIBUTE_HAS_VALUE ""
    PASSED -> AttributeKeeper_4
AttributeKeeper_4
    KEEP_ATTRS = metadatastate_id,fme_where
    -> jos_sdi_metadata (writer MYSQL_DB_1)
Note: jos_sdi_metadata
jos_sdi_metadata (writer MYSQL_DB_1)
    attributes: metadatastate_id int
