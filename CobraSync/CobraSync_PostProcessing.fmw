FME workspace CobraSync_PostProcessing.fmw
Title: CobraSync_PostProcessing

Parameters:
- MYSQL_HOST =
- MYSQL_PORT =
- MYSQL_DATABASE =
- MYSQL_USERNAME =
- MYSQL_PASSWORD =
- GUIDCOL_FFS =
- GDBP_DATABASE =
- GDBP_USERNAME =
- GDBP_PASSWORD =
- LOGFILE =   # Logfile

Readers:
- MYSQL_DB_1: MYSQL_DB from $(MYSQL_DATABASE)
- FFS_1: FFS from $(GUIDCOL_FFS)
- ORACLE_NONSPATIAL_1: ORACLE_NONSPATIAL from $(GDBP_DATABASE)

Writers:
- MYSQL_DB_2: MYSQL_DB to $(MYSQL_DATABASE)
- ORACLE_NONSPATIAL_2: ORACLE_NONSPATIAL to $(GDBP_DATABASE)

Note: GDBP.GEOPRODUKTE
GDBP.GEOPRODUKTE (reader ORACLE_NONSPATIAL_1)
    attributes: ID_GEOPRODUKT number(38,0), ID_GEODBMETA varchar2(36), LINK_METADATEN varchar2(300), CODE varchar2(8), TITLE varchar2(250), ERSTELLUNGSDATUM date, NACHFUEHRUNGSDATUM date, ID_NACHFUEHRZYKLUS number(38,0), KEINE_NACHFUEHRUNG char(1), IST_NICHT_MEHR_RELEVANT char(1), DATUM_NAECHSTE_NACHFUEHRUNGA date, DATUM_NAECHSTE_NACHFUEHRUNGM date, BEMERKUNG_NACHFUEHRUNG_INTERN varchar2(250), ZEITSTAND_JAHR number(4,0), ZEITSTAND_VERSION number(2,0), ID_ARTGEODATEN number(38,0), ID_GP_FALL number(38,0), DB_ROLLEN varchar2(250), AUTOLOAD_WERTETABELLE varchar2(500), DEFINITION_QUERY varchar2(250), AUFNAHME_GEODB_REGULAERES_GP char(1), BEMERKUNG_ZUM_GEOPRODUKT varchar2(250), ID_KONTAKT number(38,0), ID_KONTAKT1 number(38,0), DATENBEZUGSTE_AKTU_ORIENTIERT char(1), ID_KONTAKT2 number(38,0), ID_KONTAKT3 number(38,0), ID_KONTAKT4 number(38,0), ID_KONTAKT5 number(38,0), ARBEITSTARTDATUM_NORMIERUNG date,
      FREIGABEDATUM_NORMIERUNG date, ARBEITSTARTDATUM_IMPORT date, FREIGABEDATUM_IMPORT date, GEWUENSCHTES_WIPPENDATUM date, FREIGABEDATUM_GEODB_WIPPE date, FREIGABEDATUM_J date, FREIGABEDATUM_GP_DOWNLOAD date, BEMERKUNG_DATENPFLEGEPFAD varchar2(350), DATENVERTRAGSNUMMER varchar2(250), ID_STATUSGEODATEN number(38,0), ABLAGE_IN_GEODB char(1), ID_PRIORITAET number(38,0), LIEFERDATUM date, BEMERKUNG_BEZUG varchar2(250), ID_KONTAKT6 number(38,0), BEMERKUNG_HALTUNG varchar2(500), BEMERKUNG_VERTRIEB varchar2(500), BEMERKUNG_NORMIERUNG varchar2(500), LV95_FREIGABE_TRANSFO date, LV95_GP_REG_AKT_SPERREN char(1), LV95_TRANSFO_AUSGEFUEHRT date, LV95_QS_ERFOLGREICH date, LV95_KONTROLLE_LYR_DURCH_DH date, TASK_ID number(38,0), BEMERKUNG_DATENBEZUGSTELLE varchar2(250), ID_GP_AKTTYP number(38,0), TITLE_FR varchar2(250), STATUS_GP_DAT number(38,0), CACHE number(38,0), ARBEITSTARTDATUM_DAT date,
      BEMERKUNG_DAT varchar2(500), METHODIK_DOK varchar2(250), QAREGELN varchar2(1)
    -> AttributeKeeper_5
AttributeKeeper_5
    KEEP_ATTRS = ID_GEOPRODUKT,ID_KONTAKT5
    -> FeatureMerger_3 [REQUESTOR]
Note: GDBP.KONTAKTE
GDBP.KONTAKTE (reader ORACLE_NONSPATIAL_1)
    attributes: ID_KONTAKT number(38,0), ID_COBRA number(38,0), AMT varchar2(250), ID_AMTTYP number(38,0), DIENSTELLE varchar2(250), VORNAME varchar2(50), NACHNAME varchar2(50), EMAIL_ADRESSE varchar2(50), ID_KONTAKT1 number(38,0), KUERZEL varchar2(4), FIRMA3 varchar2(250), STATUS varchar2(10), DIREKTION varchar2(50), ID_GEODBMETA varchar2(36), UPDATED timestamp
    -> AttributeKeeper_6
AttributeKeeper_6
    KEEP_ATTRS = ID_KONTAKT1,ID_KONTAKT
    -> BulkAttributeRenamer
BulkAttributeRenamer
    ATTRCHOICE = All Attributes
    PATTERN_ACTION_DISP = ADDPREFIX
    MODE_CHOICE = RENAME
    REPLACE_STR = kontakte_
    -> FeatureMerger_3 [SUPPLIER]
FeatureMerger_3
    SUPPLIERS_FIRST = No
    REJECT_NULL_MISSING_KEYS = No
    IGNORE_NULLS = No
    PROCESS_DUPS = No
    MERGE_TYPE = Attributes Only
    ATTR_ACCUM_MODE = Merge Supplier
    ATTR_CONFLICT_RES = Use Requestor
    JOIN_KEYS = @Value(ID_KONTAKT5) @Value(kontakte_ID_KONTAKT) AUTO
    MERGED -> AttributeRemover
    NOT_MERGED -> AttributeCreator
AttributeRemover
    REMOVE_ATTRS = kontakte_ID_KONTAKT,ID_KONTAKT5
    -> AttributeRenamer_3
AttributeRenamer_3
    ATTR_TABLE = RENAME_SET_DEFAULT kontakte_ID_KONTAKT1 > ID_KONTAKT1
    -> AttributeCreator_2
AttributeCreator
    ATTR_TABLE = SET_TO ID_KONTAKT1
    -> AttributeRemover_2
AttributeRemover_2
    REMOVE_ATTRS = ID_KONTAKT5
    -> AttributeCreator_2
AttributeCreator_2
    ATTR_TABLE:
      SET_TO fme_where = ID_GEOPRODUKT=@Value(ID_GEOPRODUKT)
      SET_TO fme_db_operation = UPDATE
    -> GDBP.GEOPRODUKTE (writer ORACLE_NONSPATIAL_2)
GDBP.GEOPRODUKTE (writer ORACLE_NONSPATIAL_2)
    attributes: ID_KONTAKT1 number(38,0)

Bookmark: GeoDBmeta
  In den Tabellen jos_sdi_metadata (version_id) und jos_sdi_version (resource_id) sind Foreign Keys auf andere Tabellen enthalten. Die korrekten IDs sind aber erst bekannt, wenn die Features in die DB geschrieben wurden. Also nicht zur Laufzeit der Workbench! Deshalb werden temporäre IDs geschrieben sowie alle beteiligten UUIDs in ein temporäres FFS-File geschrieben. Dieses File wird im Anschluss an diese Workbench von dieser Workbench eingelesen und trägt die korrekten IDs in die Tabellen ein.
Note: jos_sdi_version
jos_sdi_version (reader MYSQL_DB_1)
    attributes: id int, guid varchar(36), alias varchar(50), created_by int, created datetime, modified_by int, modified datetime, ordering int, state tinyint, checked_out int, checked_out_time datetime, name varchar(255), resource_id int, access int, asset_id int
    -> AttributeKeeper
AttributeKeeper
    KEEP_ATTRS = guid,id
    -> AttributeRenamer
AttributeRenamer
    ATTR_TABLE:
      RENAME_SET_DEFAULT id > version_id
      RENAME_SET_DEFAULT guid > guid_version
    -> FeatureMerger [SUPPLIER]
GUIDCOL (reader FFS_1)
    attributes: guid_meta varchar(37), guid_obj varchar(36), guid_ver varchar(36)
    -> FeatureMerger [REQUESTOR]
    -> FeatureMerger_2 [REQUESTOR]
FeatureMerger
    SUPPLIERS_FIRST = No
    REJECT_NULL_MISSING_KEYS = No
    IGNORE_NULLS = No
    PROCESS_DUPS = No
    MERGE_TYPE = Attributes Only
    ATTR_ACCUM_MODE = Merge Supplier
    ATTR_CONFLICT_RES = Use Requestor
    JOIN_KEYS = @Value(guid_ver) @Value(guid_version) AUTO
    MERGED -> StringConcatenator
StringConcatenator
    VAL_ATTR = fme_where
    ACTION = Create New Attribute
    PARM_LINE = guid='@Value(guid_meta)'
    -> AttributeKeeper_3
AttributeKeeper_3
    KEEP_ATTRS = fme_where,version_id
    -> jos_sdi_metadata (writer MYSQL_DB_2)
Note: jos_sdi_metadata
jos_sdi_metadata (writer MYSQL_DB_2)
    attributes: version_id int
Note: jos_sdi_resource
jos_sdi_resource (reader MYSQL_DB_1)
    attributes: id int, guid varchar(36), alias varchar(50), created_by int, created datetime, modified_by int, modified datetime, ordering int, state tinyint, checked_out int, checked_out_time datetime, name varchar(255), description varchar(500), organism_id int, resourcetype_id int, accessscope_id int, access int, asset_id int
    -> AttributeKeeper_2
AttributeKeeper_2
    KEEP_ATTRS = guid,id
    -> AttributeRenamer_2
AttributeRenamer_2
    ATTR_TABLE:
      RENAME_SET_DEFAULT id > resource_id
      RENAME_SET_DEFAULT guid > guid_object
    -> FeatureMerger_2 [SUPPLIER]
FeatureMerger_2
    SUPPLIERS_FIRST = No
    REJECT_NULL_MISSING_KEYS = No
    IGNORE_NULLS = No
    PROCESS_DUPS = No
    MERGE_TYPE = Attributes Only
    ATTR_ACCUM_MODE = Merge Supplier
    ATTR_CONFLICT_RES = Use Requestor
    JOIN_KEYS = @Value(guid_obj) @Value(guid_object) AUTO
    MERGED -> StringConcatenator_2
StringConcatenator_2
    VAL_ATTR = fme_where
    ACTION = Create New Attribute
    PARM_LINE = guid='@Value(guid_ver)'
    -> AttributeKeeper_4
AttributeKeeper_4
    KEEP_ATTRS = fme_where,resource_id
    -> jos_sdi_version (writer MYSQL_DB_2)
Note: jos_sdi_version
jos_sdi_version (writer MYSQL_DB_2)
    attributes: resource_id int
